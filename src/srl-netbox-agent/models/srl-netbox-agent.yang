module netbox-agent {

    yang-version "1";

    // namespace
    namespace "urn:srl_test/netbox-agent";

    prefix "netbox_agent";

    revision "2021-10-27" {
        description "Initial revision";
        reference "TBD";
    }

    grouping netbox-agent-top {
        description "Top level grouping for Netbox agent sample app";

        container netbox-agent {
            presence "presence container";

            description "Top level enclosing container for netbox agent sample app
                         config and operational state data";

            leaf admin-state {
              type enumeration {
               enum enable;
               enum disable;
              }
              mandatory true;
            }

            leaf airflow {
              type enumeration {
               enum B2F;
               enum F2B;
              }
              default "F2B";
            }

            leaf power {
              type enumeration {
               enum AC;
               enum DC;
              }
              default "AC";
            }

            leaf netbox-url {
              description "URL for Netbox server";
              type string;
              default "http://172.20.20.1:8000";
            }

            leaf netbox-user {
              description "Netbox user to authenticate as";
              type string;
              default "admin";
            }

            leaf netbox-password {
              description "Netbox password to authenticate with";
              type string;
              default "admin";
            }

            leaf netbox-token {
              description "Security token to use with Netbox server";
              type string;
            }
        }
    }

    // data definition statements
    uses netbox-agent-top;
}
